package OpticalTransceiverReferenceModel {
  doc /* Workspace import hub for the optical transceiver reference model. */

  private import Project::*;
  private import ProjectLibrary::*;
  private import TransceiverContext::*;
  private import StakeholdersAndNeeds::*;
  private import BoundaryRequirements::*;
  private import TransmitRequirements::*;
  private import Behavior::*;
  private import Architecture::*;
  private import Analysis::*;
  private import Verification::*;
  private import ProjectViews::*;
}
