package Architecture {
  doc /* EI-002 selected transmitter-first logical architecture. */

  private import TransceiverContext::*;
  private import TransmitRequirements::*;
  private import Behavior::*;
  private import ProjectLibrary::*;
  private import Elan8::Method::Core::*;

  part def TransmitElectronics {
    @EngineeringConcern { concern = architecture; }
    @AbstractionLevel { level = logical; }

    port txDataInput : ~DigitalDataPort;
    port modulatorDriveOutput : ModulatorDrivePort;

    perform action encodeData : EncodeTransmitData;
    perform action generateDrive : GenerateModulatorDrive;
  }

  part def MachZehnderModulator {
    @EngineeringConcern { concern = architecture; }
    @AbstractionLevel { level = logical; }

    attribute insertionLossDb : OpticalLossDb;

    port carrierInput : ~OpticalCarrierPort;
    port driveInput : ~ModulatorDrivePort;
    port modulatedOutput : OpticalDataPort;

    perform action modulateCarrier : ModulateOpticalCarrier;
  }

  part def OutputFibreCoupler {
    @EngineeringConcern { concern = architecture; }
    @AbstractionLevel { level = logical; }

    attribute insertionLossDb : OpticalLossDb;

    port picInput : ~OpticalDataPort;
    port fibreOutput : OpticalDataPort;

    perform action coupleOutput : CoupleModulatedOpticalOutput;
  }

  part def OpticalTransmitter {
    @EngineeringConcern { concern = architecture; }
    @AbstractionLevel { level = logical; }
    @DecisionRecord {
      decisionId = "ADR-001";
      title = "Use an NRZ/OOK Mach-Zehnder transmitter";
      rationale = "Provides a focused transmitter-first path with explicit electrical drive, optical modulation, and replaceable fibre coupling responsibilities.";
    }
    @Assumption {
      assumptionId = "ASM-001";
      statement = "The external laser supplies a suitable continuous-wave carrier near 1550 nm; carrier generation and laser control remain outside the module.";
      valid = true;
    }

    attribute internalRoutingLossDb : OpticalLossDb = 1.0;

    port electricalDataInput : ~DigitalDataPort;
    port opticalCarrierInput : ~OpticalCarrierPort;
    port modulatedOpticalOutput : OpticalDataPort;

    part transmitElectronics : TransmitElectronics;
    part modulator : MachZehnderModulator {
      attribute :>> insertionLossDb = 4.5;
    }
    part outputCoupler : OutputFibreCoupler {
      attribute :>> insertionLossDb = 2.0;
    }

    bind electricalDataInput = transmitElectronics.txDataInput;
    bind opticalCarrierInput = modulator.carrierInput;
    bind outputCoupler.fibreOutput = modulatedOpticalOutput;

    connect transmitElectronics.modulatorDriveOutput to modulator.driveInput;
    connect modulator.modulatedOutput to outputCoupler.picInput;

    perform action transmitOpticalData : TransmitOpticalData;
    allocate transmitOpticalData.encodeData to transmitElectronics;
    allocate transmitOpticalData.generateDrive to transmitElectronics;
    allocate transmitOpticalData.modulateCarrier to modulator;
    allocate transmitOpticalData.coupleOutput to outputCoupler;
  }

  part def TransmitterFirstOpticalTransceiver :> OpticalTransceiverModule {
    @EngineeringConcern { concern = architecture; }
    @AbstractionLevel { level = system; }

    attribute :>> opticalTxOutputPowerDbm = -4.5;

    part transmitter : OpticalTransmitter;

    bind electricalTxDataInput = transmitter.electricalDataInput;
    bind opticalCarrierInput = transmitter.opticalCarrierInput;
    bind transmitter.modulatedOpticalOutput = opticalTxOutput;

    doc /*
      EI-002 realizes the transmit path. The inherited receive, power, and
      management boundary features remain part of the system contract, while
      their internal realization is deferred to later engineering increments.
    */
  }

  part transceiverSystem : TransmitterFirstOpticalTransceiver;

  satisfy transmitConversionSpecification by transceiverSystem;
  satisfy minimumTransmitOutputPower by transceiverSystem.opticalTxOutputPowerDbm;
}
